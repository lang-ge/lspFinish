;;;==================================================*
;;;[功能] 字符串倒序
;;;测试：(reve (getstring "输入数字 "))
(defun reve (s / n a d1)
  (setq n (strlen s))
  (setq a "")
  (repeat n
    (setq d1 (chr (vl-string-elt s (1- n))))
    (setq a (strcat a d1))
    (setq n (1- n))
  )
  (alert (strcat "倒序是：" a))
  (princ)
)
