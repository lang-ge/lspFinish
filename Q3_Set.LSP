;;;      通用函数                                                   *
;;;功能：数据表写入文件                                             *
(defun Dcl-Writ (lst nete / dcl_file file str dcl_id dcl-name)
 (vl-load-com)
 (setq dcl_file (vl-filename-mktemp "Zyd" nil nete))
 (setq file (open dcl_file "w"))
 (foreach str lst
  (write-line str file)
 )
 (close file)
 dcl_file
)
;;;附属文件生成!
(setq MJZ1 '("	mjzca:dialog {	"
"	    label = \"M-钣金工具\" ;	"
"	    :row {	"
"	        :button {	"
"	            key = \"Q1\" ;	"
"	            label = \"长度统计\" ;	"
"	            width = 20 ;	"
"	        }	"
"	        :button {	"
"	            key = \"Q5\" ;	"
"	            label = \"重复去除\" ;	"
"	            width = 20 ;	"
"	        }	"
"	    }	"
"	    :row {	"
"	        :button {	"
"	            key = \"Q2\" ;	"
"	            label = \"面积计算\" ;	"
"	            width = 20 ;	"
"	        }	"
"	        :button {	"
"	            key = \"Q6\" ;	"
"	            label = \"超级打断\" ;	"
"	            width = 20 ;	"
"	        }	"
"	    }	"
"	    :row {	"
"	        :button {	"
"	            key = \"Q3\" ;	"
"	            label = \"钣金报价\" ;	"
"	            width = 20 ;	"
"	        }	"
"	        :button {	"
"	            key = \"Q7\" ;	"
"	            label = \"激光报价\" ;	"
"	            width = 20 ;	"
"	        }	"
"	    }	"
"	    :row {	"
"	        :button {	"
"	            key = \"Q4\" ;	"
"	            label = \"属性导入\" ;	"
"	            width = 20 ;	"
"	        }	"
"	        :button {	"
"	            key = \"Q8\" ;	"
"	            label = \"creo-Y因子\" ;	"
"	            width = 20 ;	"
"	        }	"
"	    }	"
"	    :row {	"
"	        :button {	"
"	            key = \"Q9\" ;	"
"	            label = \"属性-bom\" ;	"
"	            width = 20 ;	"
"	        }	"
"	        :button {	"
"	            key = \"Q10\" ;	"
"	            label = \"待扩充<<<\" ;	"
"	            width = 20 ;	"
"	        }	"
"	    }	"
"	    ok_only;	"
"	}	"
"		"
"	q2:dialog {	"
"	    label = \"面积计算\" ;	"
"	    :boxed_row {	"
"	        label = \"类别:\" ;	"
"	        :radio_button {	"
"	            key = \"PS\" ;	"
"	            label = \"平面积\" ;	"
"	            value = \"1\" ;	"
"	        }	"
"	        :radio_button {	"
"	            key = \"FS\" ;	"
"	            label = \"表面积\" ;	"
"	        }	"
"	    }	"
"	    :row {	"
"	        :boxed_column {	"
"	            label = \"单位:\" ;	"
"	            :radio_button {	"
"	                key = \"MM\" ;	"
"	                label = \"毫米\" ;	"
"	                value = \"1\" ;	"
"	            }	"
"	            :radio_button {	"
"	                key = \"M\" ;	"
"	                label = \"米\" ;	"
"	            }	"
"	        }	"
"	        :boxed_column {	"
"	            label = \"参数:\" ;	"
"	            :popup_list {	"
"	                edit_width = 4 ;	"
"	                key = \"Acy\" ;	"
"	                label = \"精度\" ;	"
"	                list = \"1\\n2\\n3\\n4\\n5\\n6\" ;	"
"	                value = \"1\" ;	"
"	            }	"
"	            :popup_list {	"
"	                edit_width = 4 ;	"
"	                key = \"PT\" ;	"
"	                label = \"厚度\" ;	"
"	                list = \"0.8\\n1.0\\n1.2\\n1.5\\n2.0\\n2.5\\n3.0\" ;	"
"	            }	"
"	        }	"
"	    }	"
"	    ok_cancel;	"
"	}	"
"		"
"	q3_date:dialog {	"
"	    label = \"★★钣金报价排版系统V1.5★★\" ;	"
"	    :row {	"
"	        :column {	"
"	            :boxed_column {	"
"	                key = \"PN_1\" ;	"
"	                label = \"工件尺寸\" ;	"
"	                :edit_box {	"
"	                    edit_limit = 6 ;	"
"	                    edit_width = 6 ;	"
"	                    key = \"A1\" ;	"
"	                    label = \"X方向最大长度(X):\" ;	"
"	                    mnemonic = \"X\" ;	"
"	                }	"
"	                :edit_box {	"
"	                    edit_limit = 6 ;	"
"	                    edit_width = 6 ;	"
"	                    key = \"B1\" ;	"
"	                    label = \"Y方向最大长度(Y):\" ;	"
"	                    mnemonic = \"Y\" ;	"
"	                }	"
"	            }	"
"	            :boxed_column {	"
"	                key = \"PN_2\" ;	"
"	                label = \"工件资料\" ;	"
"	                :row {	"
"	                    :edit_box {	"
"	                        edit_limit = 10 ;	"
"	                        edit_width = 10 ;	"
"	                        key = \"prtna\" ;	"
"	                        label = \"工件名称(N):\" ;	"
"	                        mnemonic = \"N\" ;	"
"	                    }	"
"	                    :column {	"
"	                        :spacer {	"
"	                            fixed_height = true ;	"
"	                            fixed_width = true ;	"
"	                            width = 0.1 ;	"
"	                        }	"
"	                        :image_button {	"
"	                            color = red ;	"
"	                            fixed_width = true ;	"
"	                            key = \"picna\" ;	"
"	                            width = 3.3 ;	"
"	                        }	"
"	                    }	"
"	                }	"
"	                :row {	"
"	                    :edit_box {	"
"	                        edit_limit = 10 ;	"
"	                        edit_width = 10 ;	"
"	                        key = \"prtma\" ;	"
"	                        label = \"工件材质(M):\" ;	"
"	                        mnemonic = \"M\" ;	"
"	                    }	"
"	                    :column {	"
"	                        :spacer {	"
"	                            fixed_height = true ;	"
"	                            fixed_width = true ;	"
"	                            width = 0.1 ;	"
"	                        }	"
"	                        :image_button {	"
"	                            color = yellow ;	"
"	                            fixed_width = true ;	"
"	                            key = \"picma\" ;	"
"	                            width = 3.3 ;	"
"	                        }	"
"	                    }	"
"	                }	"
"	                :row {	"
"	                    :edit_box {	"
"	                        edit_limit = 10 ;	"
"	                        edit_width = 10 ;	"
"	                        key = \"prtth\" ;	"
"	                        label = \"工件料厚(T): \" ;	"
"	                        mnemonic = \"T\" ;	"
"	                    }	"
"	                    :column {	"
"	                        :spacer {	"
"	                            fixed_height = true ;	"
"	                            fixed_width = true ;	"
"	                            width = 0.1 ;	"
"	                        }	"
"	                        :image_button {	"
"	                            color = dialog_background ;	"
"	                            fixed_width = true ;	"
"	                            key = \"picth\" ;	"
"	                            width = 3.3 ;	"
"	                        }	"
"	                    }	"
"	                }	"
"	            }	"
"	            :boxed_column {	"
"	                label = \"自动选取工件\" ;	"
"	                :button {	"
"	                    key = \"SEL_PRT\" ;	"
"	                    label = \"选择要处理的工件(S)<<\" ;	"
"	                    mnemonic = \"S\" ;	"
"	                }	"
"	            }	"
"	        }	"
"	        :column {	"
"	            :boxed_column {	"
"	                label = \"板材尺寸\" ;	"
"	                :radio_button {	"
"	                    key = \"PN_3_1\" ;	"
"	                    label = \"1220X1220\" ;	"
"	                    mnemonic = \"1\" ;	"
"	                    value = \"1\" ;	"
"	                }	"
"	                :radio_button {	"
"	                    key = \"PN_3_2\" ;	"
"	                    label = \"1220X2440\" ;	"
"	                    mnemonic = \"2\" ;	"
"	                }	"
"	                :radio_button {	"
"	                    key = \"PN_3_3\" ;	"
"	                    label = \"自定义(3)\" ;	"
"	                    mnemonic = \"3\" ;	"
"	                }	"
"	                :row {	"
"	                    :edit_box {	"
"	                        edit_limit = 4 ;	"
"	                        edit_width = 4 ;	"
"	                        key = \"lh\" ;	"
"	                        label = \"X方向板材尺寸(L):       \" ;	"
"	                        mnemonic = \"L\" ;	"
"	                    }	"
"	                    :column {	"
"	                        :spacer {	"
"	                            fixed_height = true ;	"
"	                            fixed_width = true ;	"
"	                            width = 0.1 ;	"
"	                        }	"
"	                        :image_button {	"
"	                            aspect_ratio = 1 ;	"
"	                            fixed_width = true ;	"
"	                            key = \"piL\" ;	"
"	                            width = 3.5 ;	"
"	                        }	"
"	                    }	"
"	                }	"
"	                :row {	"
"	                    :edit_box {	"
"	                        edit_limit = 4 ;	"
"	                        edit_width = 4 ;	"
"	                        key = \"wh\" ;	"
"	                        label = \"Y方向板材尺寸(V):       \" ;	"
"	                        mnemonic = \"V\" ;	"
"	                    }	"
"	                    :column {	"
"	                        :spacer {	"
"	                            fixed_height = true ;	"
"	                            fixed_width = true ;	"
"	                            width = 0.1 ;	"
"	                        }	"
"	                        :image_button {	"
"	                            aspect_ratio = 1 ;	"
"	                            fixed_width = true ;	"
"	                            key = \"piW\" ;	"
"	                            width = 3.5 ;	"
"	                        }	"
"	                    }	"
"	                }	"
"	            }	"
"	            :boxed_column {	"
"	                label = \"间距设定\" ;	"
"	                :edit_box {	"
"	                    edit_limit = 2 ;	"
"	                    edit_width = 4 ;	"
"	                    key = \"prtph\" ;	"
"	                    label = \"工件排版间距(P):\" ;	"
"	                    mnemonic = \"P\" ;	"
"	                    value = \"5\" ;	"
"	                }	"
"	                :edit_box {	"
"	                    edit_limit = 2 ;	"
"	                    edit_width = 4 ;	"
"	                    key = \"Ah\" ;	"
"	                    label = \"夹钳安全间距(A):\" ;	"
"	                    mnemonic = \"A\" ;	"
"	                    value = \"80\" ;	"
"	                }	"
"	            }	"
"	            :row {	"
"	                alignment = right ;	"
"	                fixed_width = true ;	"
"	                :toggle {	"
"	                    key = \"OP\" ;	"
"	                    label = \"PrSet\" ;	"
"	                    mnemonic = \"O\" ;	"
"	                }	"
"	                :toggle {	"
"	                    key = \"OPS\" ;	"
"	                    label = \"Mview\" ;	"
"	                }	"
"	                :image_button {	"
"	                    aspect_ratio = 1 ;	"
"	                    color = 3 ;	"
"	                    fixed_width = true ;	"
"	                    key = \"makDate\" ;	"
"	                    label = \"成本信息(D)\" ;	"
"	                    mnemonic = \"D\" ;	"
"	                    width = 3 ;	"
"	                }	"
"	                :text {	"
"	                    label = \"成本信息(D)\" ;	"
"	                }	"
"	            }	"
"	        }	"
"	        :column {	"
"	            :boxed_row {	"
"	                children_fixed_width = true ;	"
"	                label = \"偏置\" ;	"
"	                :column {	"
"	                    :text {	"
"	                        label = \"从原点\" ;	"
"	                    }	"
"	                    :edit_box {	"
"	                        edit_width = 3 ;	"
"	                        key = \"BaX\" ;	"
"	                        label = \"  dX:\" ;	"
"	                    }	"
"	                    :edit_box {	"
"	                        edit_width = 3 ;	"
"	                        key = \"BaY\" ;	"
"	                        label = \"  dY:\" ;	"
"	                    }	"
"	                }	"
"	                :column {	"
"	                    :text {	"
"	                        label = \"从终点\" ;	"
"	                    }	"
"	                    :edit_box {	"
"	                        edit_width = 3 ;	"
"	                        key = \"EnX\" ;	"
"	                        label = \"  dX:\" ;	"
"	                        value = \"20\" ;	"
"	                    }	"
"	                    :edit_box {	"
"	                        edit_width = 3 ;	"
"	                        key = \"EnY\" ;	"
"	                        label = \"  dY:\" ;	"
"	                        value = \"-10\" ;	"
"	                    }	"
"	                }	"
"	            }	"
"	            :image_button {	"
"	                aspect_ratio = 5 ;	"
"	                color = red ;	"
"	                fixed_width = true ;	"
"	                height = 0.3 ;	"
"	                key = \"pick1\" ;	"
"	            }	"
"	            :boxed_row {	"
"	                key = \"XyN\" ;	"
"	                label = \"数量\" ;	"
"	                :edit_box {	"
"	                    edit_width = 3 ;	"
"	                    key = \"XN\" ;	"
"	                    label = \"   X:\" ;	"
"	                    mnemonic = \"L\" ;	"
"	                }	"
"	                :edit_box {	"
"	                    edit_width = 3 ;	"
"	                    key = \"YN\" ;	"
"	                    label = \"   Y:\" ;	"
"	                    mnemonic = \"V\" ;	"
"	                }	"
"	            }	"
"	            :image_button {	"
"	                aspect_ratio = 5 ;	"
"	                color = red ;	"
"	                fixed_width = true ;	"
"	                height = 0.3 ;	"
"	                key = \"pick2\" ;	"
"	            }	"
"	            :boxed_column {	"
"	                children_alignment = left ;	"
"	                children_fixed_width = true ;	"
"	                key = \"P S G\" ;	"
"	                label = \"Sheet Area and Weight\" ;	"
"	                :row {	"
"	                    :edit_box {	"
"	                        edit_width = 5 ;	"
"	                        key = \"PS\" ;	"
"	                        label = \"    面积\" ;	"
"	                    }	"
"	                    :text {	"
"	                        label = \"sq.m\" ;	"
"	                    }	"
"	                }	"
"	                :row {	"
"	                    :edit_box {	"
"	                        edit_width = 5 ;	"
"	                        key = \"PG\" ;	"
"	                        label = \"    重量\" ;	"
"	                    }	"
"	                    :text {	"
"	                        label = \"kg\" ;	"
"	                    }	"
"	                }	"
"	            }	"
"	            :image_button {	"
"	                aspect_ratio = 5 ;	"
"	                color = red ;	"
"	                height = 0.01 ;	"
"	                key = \"pick3\" ;	"
"	            }	"
"	        }	"
"	    }	"
"	    :row {	"
"	        :spacer {}	"
"	        :spacer {}	"
"	        :spacer {}	"
"	        :button {	"
"	            key = \"modDate\" ;	"
"	            label = \"帮助(H)\" ;	"
"	            mnemonic = \"H\" ;	"
"	        }	"
"	        :button {	"
"	            key = \"simDate\" ;	"
"	            label = \"排版模拟(R)\" ;	"
"	            mnemonic = \"R\" ;	"
"	        }	"
"	        :retirement_button {	"
"	            is_cancel = true ;	"
"	            key = \"cancel\" ;	"
"	            label = \"  取 消  \" ;	"
"	        }	"
"	        :spacer {}	"
"	        :spacer {}	"
"	        :spacer {}	"
"	    }	"
"	    :row {	"
"	        :column {	"
"	            :text {	"
"	                label = \"作者：浪子   更多CAD插件访问 http://zhenyoudong1.blog.163.com/\" ;	"
"	            }	"
"	            :text {	"
"	                label = \"2014年1月5日  于  深圳公明楼村\" ;	"
"	            }	"
"	        }	"
"	        :icon_image {	"
"	            aspect_ratio = 0.2 ;	"
"	            color = white ;	"
"	            key = \"Display\" ;	"
"	            width = 27.5 ;	"
"	        }	"
"	    }	"
"	}	"
"		"
"	q3_output:dialog {	"
"	    label = \"排版信息输出\" ;	"
"	    :concatenation {	"
"	        :text {	"
"	            key = \"wenzi\" ;	"
"	            width = 30 ;	"
"	        }	"
"	    }	"
"	    :concatenation {	"
"	        :text_part {	"
"	            label = \"   材料费用为:\" ;	"
"	        }	"
"	        :text {	"
"	            is_bold = true ;	"
"	            key = \"v1\" ;	"
"	            width = 6 ;	"
"	        }	"
"	        :text_part {	"
"	            label = \"元\" ;	"
"	        }	"
"	    }	"
"	    :concatenation {	"
"	        :text {	"
"	            key = \"wenzA\" ;	"
"	            width = 32 ;	"
"	        }	"
"	    }	"
"	    :concatenation {	"
"	        :text_part {	"
"	            label = \"   喷涂费用为:\" ;	"
"	        }	"
"	        :text {	"
"	            is_bold = true ;	"
"	            key = \"v2\" ;	"
"	            width = 6 ;	"
"	        }	"
"	        :text_part {	"
"	            label = \"元\" ;	"
"	        }	"
"	    }	"
"	    :concatenation {	"
"	        :text_part {	"
"	            label = \" ◇材料排版核算:\" ;	"
"	        }	"
"	        :text {	"
"	            is_bold = true ;	"
"	            key = \"str1\" ;	"
"	            width = 6 ;	"
"	        }	"
"	        :text_part {	"
"	            label = \"*\" ;	"
"	        }	"
"	        :text {	"
"	            is_bold = true ;	"
"	            key = \"str2\" ;	"
"	            width = 6 ;	"
"	        }	"
"	    }	"
"	    :concatenation {	"
"	        :text_part {	"
"	            label = \"   横向:\" ;	"
"	        }	"
"	        :text {	"
"	            is_bold = true ;	"
"	            key = \"v3\" ;	"
"	            width = 3 ;	"
"	        }	"
"	        :text_part {	"
"	            label = \"件\" ;	"
"	        }	"
"	        spacer;	"
"	        :text_part {	"
"	            label = \"纵向:\" ;	"
"	        }	"
"	        :text {	"
"	            is_bold = true ;	"
"	            key = \"v4\" ;	"
"	            width = 3 ;	"
"	        }	"
"	        :text_part {	"
"	            label = \"件\" ;	"
"	        }	"
"	    }	"
"	    :concatenation {	"
"	        :spacer {}	"
"	        :text {	"
"	            is_bold = true ;	"
"	            key = \"propose\" ;	"
"	            width = 30 ;	"
"	        }	"
"	    }	"
"	    ok_only;	"
"	}	"
"		"
"	q3_las:dialog {	"
"	    label = \"Laser Quote Tool\" ;	"
"	    :column {	"
"	        :boxed_row {	"
"	            children_fixed_width = true ;	"
"	            label = \"数据显示\" ;	"
"	            :column {	"
"	                :text {	"
"	                    label = \"数据一\" ;	"
"	                }	"
"	                :edit_box {	"
"	                    edit_width = 6 ;	"
"	                    key = \"BaX\" ;	"
"	                    label = \"切割单价<元/m>:\" ;	"
"	                    value = \"1.0\" ;	"
"	                }	"
"	                :edit_box {	"
"	                    edit_width = 6 ;	"
"	                    key = \"BaY\" ;	"
"	                    label = \"穿刺单价<元/个>:\" ;	"
"	                    value = \"0.1\" ;	"
"	                }	"
"	            }	"
"	            :column {	"
"	                :text {	"
"	                    label = \"数据二\" ;	"
"	                }	"
"	                :edit_box {	"
"	                    edit_width = 6 ;	"
"	                    key = \"EnX\" ;	"
"	                    label = \"切割长度/m:\" ;	"
"	                    value = \"20\" ;	"
"	                }	"
"	                :edit_box {	"
"	                    edit_width = 6 ;	"
"	                    key = \"EnY\" ;	"
"	                    label = \"穿刺个数/P:\" ;	"
"	                    value = \"-10\" ;	"
"	                }	"
"	            }	"
"	        }	"
"	        :image_button {	"
"	            aspect_ratio = 5 ;	"
"	            color = red ;	"
"	            fixed_width = true ;	"
"	            height = 0.3 ;	"
"	            key = \"pick1\" ;	"
"	        }	"
"	        :boxed_row {	"
"	            key = \"PN_2\" ;	"
"	            label = \"数据设置\" ;	"
"	            :popup_list {	"
"	                edit_width = 12 ;	"
"	                key = \"prtma\" ;	"
"	                label = \"材质(M):\" ;	"
"	                mnemonic = \"M\" ;	"
"	            }	"
"	            :popup_list {	"
"	                edit_width = 12 ;	"
"	                key = \"prtth\" ;	"
"	                label = \"料厚(T):\" ;	"
"	                mnemonic = \"T\" ;	"
"	            }	"
"	            :boxed_column {	"
"	                label = \"报价:\" ;	"
"	                :radio_button {	"
"	                    key = \"sin\" ;	"
"	                    label = \"单个\" ;	"
"	                    value = \"1\" ;	"
"	                }	"
"	                :radio_button {	"
"	                    key = \"all\" ;	"
"	                    label = \"全部\" ;	"
"	                }	"
"	            }	"
"	        }	"
"	        :image_button {	"
"	            aspect_ratio = 5 ;	"
"	            color = red ;	"
"	            fixed_width = true ;	"
"	            height = 0.3 ;	"
"	            key = \"pick2\" ;	"
"	        }	"
"	        :row {	"
"	            :concatenation {	"
"	                :text_part {	"
"	                    label = \"切割总报价为:\" ;	"
"	                }	"
"	                :text {	"
"	                    is_bold = true ;	"
"	                    key = \"Av\" ;	"
"	                    width = 6 ;	"
"	                }	"
"	                :text_part {	"
"	                    label = \"元\" ;	"
"	                }	"
"	            }	"
"	            :button {	"
"	                is_default = true ;	"
"	                key = \"makDate\" ;	"
"	                label = \"报价计算<<<\" ;	"
"	                width = 3 ;	"
"	            }	"
"	            cancel_button;	"
"	        }	"
"	        :text {	"
"	            label = \"★ 程序制作 浪子 QQ 112807662\" ;	"
"	        }	"
"	    }	"
"	}	"
"		"
"	q3_help:dialog {	"
"	    label = \"排版系统-帮助\" ;	"
"	    :boxed_row {	"
"	        :spacer {}	"
"	        :spacer {}	"
"	        :spacer {}	"
"	        :text {	"
"	            alignment = centered ;	"
"	            label = \"钣金报价排版系统 V1.5 ---- 浪子，2014.07\" ;	"
"	        }	"
"	        :button {	"
"	            fixed_width = true ;	"
"	            key = \"htm\" ;	"
"	            label = \">>\" ;	"
"	        }	"
"	    }	"
"	    :list_box {	"
"	        key = \"HelpList\" ;	"
"	        width = 83 ;	"
"	        height = 24 ;	"
"	    }	"
"	    :row {	"
"	        spacer_1;	"
"	        :button {	"
"	            label = \"确定(O)\" ;	"
"	            key = \"HelpOKBtn\" ;	"
"	            is_cancel = true ;	"
"	            mnemonic = \"O\" ;	"
"	            width = 15 ;	"
"	            fixed_width = true ;	"
"	        }	"
"	        spacer_1;	"
"	    }	"
"	}	"
"		"
"	q4:dialog {	"
"	    label = \"属性导入工具v1.0\" ;	"
"	    :column {	"
"	        :row {	"
"	            :edit_box {	"
"	                key = \"na\" ;	"
"	                label = \"名称:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"ina\" ;	"
"	                    width = 3.5 ;	"
"	                }	"
"	            }	"
"	        }	"
"	        :row {	"
"	            :edit_box {	"
"	                key = \"dw\" ;	"
"	                label = \"图号:       \" ;	"
"	                mnemonic = \"V\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"idw\" ;	"
"	                    width = 3.5 ;	"
"	                }	"
"	            }	"
"	        }	"
"	        :row {	"
"	            :edit_box {	"
"	                key = \"ve\" ;	"
"	                label = \"版本:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"ive\" ;	"
"	                    width = 3.5 ;	"
"	                }	"
"	            }	"
"	        }	"
"	        :row {	"
"	            :edit_box {	"
"	                key = \"no\" ;	"
"	                label = \"数量:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"ino\" ;	"
"	                    width = 3.5 ;	"
"	                }	"
"	            }	"
"	        }	"
"	        :row {	"
"	            :edit_box {	"
"	                key = \"su\" ;	"
"	                label = \"表处:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"isu\" ;	"
"	                    width = 3.5 ;	"
"	                }	"
"	            }	"
"	        }	"
"	        :row {	"
"	            :edit_box {	"
"	                key = \"ma\" ;	"
"	                label = \"材料:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"ima\" ;	"
"	                    width = 3.5 ;	"
"	                }	"
"	            }	"
"	        }	"
"	        :row {	"
"	            :edit_box {	"
"	                key = \"th\" ;	"
"	                label = \"厚度:       \" ;	"
"	                mnemonic = \"L\" ;	"
"	            }	"
"	            :column {	"
"	                :spacer {	"
"	                    fixed_height = true ;	"
"	                    fixed_width = true ;	"
"	                    width = 0.1 ;	"
"	                }	"
"	                :image_button {	"
"	                    aspect_ratio = 1 ;	"
"	                    fixed_width = true ;	"
"	                    key = \"ith\" ;	"
"	                    width = 3.5 ;	"
"	                }	"
"	            }	"
"	        }	"
"	    }	"
"	    ok_cancel;	"
"	}	"
))




(setq MJZ2 '("	(\"切割单价\" \"材质\" \"料厚\" \"穿刺单价\")	"
"	(\"\" \"铁\" \"不锈钢\" \"铝铜\")	"
"	(\"1.0≤\"   \"1.0  0.1\" \"2.0  0.1\"  \"2.2  0.1\" )	"
"	(\"1.2\"     \"1.2  0.1\" \"2.2  0.1\"  \"2.5  0.1\" )	"
"	(\"1.5\"     \"1.5  0.1\" \"2.5  0.1\"  \"3.0  0.1\" )	"
"	(\"2.0\"     \"2.0  0.1\" \"3.2  0.1\"  \"4.5  0.1\" )	"
"	(\"2.5\"     \"2.5  0.1\" \"3.8  0.1\"  \"6.0  0.1\" )	"
"	(\"3.0\"     \"3.0  0.1\" \"4.0  0.1\"  \"6.5  0.1\" )	"
"	(\"4.0\"     \"4.0  0.15\" \"7.00  0.2\"  \"11.0  0.2\" )	"
"	(\"5.0\"     \"5.0  0.15\" \"10.0  0.2\"  \"14.0  0.2\" )	"
"	(\"6.0\"     \"6.0  0.15\" \"12.0  0.3\"  \"18.0  0.3\" )	"
"	(\"8.0\"     \"8.0  0.40\" \"18.0  0.8\"  \"40.0  0.8\" )	"
"	(\"10.0\"    \"10.0  0.5\" \"25.0  1.0\"  \"50.0  1.0\" )	"
"	(\"12.0\"     \"3.0  0.1\" \"4.5  0.5\"  \"1.5  2.0\" )	"
"	(\"15.0\"     \"3.0  0.1\" \"4.5  0.5\"  \"1.5  2.0\" )	"
"	(\"16.0\"     \"3.0  0.1\" \"4.5  0.5\"  \"1.5  2.0\" )	"
"	(\"18.0\"     \"3.0  0.1\" \"4.5  0.5\"  \"1.5  2.0\" )	"
"	(\"20.0\"     \"3.0  0.1\" \"4.5  0.5\"  \"1.5  2.0\" )	"
"	(\"25.0\"     \"3.0  0.1\" \"4.5  0.5\"  \"1.5  2.0\" )	"
))
 
(setq MJZ3 '("	名称:	"
"	(\"顶板\" \"顶盖\" \"底板\" \"底壳\" \"盒盖\" \"盒体\" \"机箱\" \"支架\")	"
"	材质:	"
"	(\"SPCC\" \"SECC\" \"SGCC\" \"AL\" \"AL6063\" \"SUS304\" \"SUS201\" )	"
"	料厚:	"
"	(\"1.0\" \"1.2\" \"1.5\" \"2.0\" \"2.5\" \"3.5\" )	"
"	----------------★底层数据设置★----------------	"
"	铝材单价:	"
"	22	"
"	铁材单价:	"
"	6	"
"	SUS 单价:	"
"	26	"
"	表处单价:	"
"	17	"
))
	 
(setq MJZ4 '("	钣金报价排版系统V1.5版	"
"		"
"	浪子，2014年01月07日	"
"		"
"	程序简介：	"
"		"
"	    这是一个为AutoCAD2004以上版本设计的钣金报价排版程序。程序根据用户输入的工件尺寸等相关资料及板料相关尺寸，实现排版模拟及成本核算评估功能。	"
"		"
"	免责声明：本程序仅提供作为应用上的参考, 而未声明或隐含任何保证；对于任何特殊用途之适应性, 以及商业销售所隐含作出的保证, 在此一概予以否认。	"
"		"
"	拒绝担保：拒绝任何责任担保，因使用该程序所致的全部风险及后果均由用户自己承担。	"
"		"
"	数据警告：程序的某些关键底层数据以当前市场行情而设 不排除随时间推移而改变！当然在后续版本会考虑自定义这些数据的！	"
"		"
"	更新历史：	"
"		"
"	·   2012/12/05: 程序的初步构思及规划	"
"		"
"	·   2013/01/20: 程序lisp部份逐步成形和完善测试！产生第一个Beta版本V1.0	"
"		"
"	·   2013/02/20: 程序正式测试完毕！升级Beta版本V1.1	"
"		"
"	·   2013/03/05: 启动DCL对话框的导入设计调试及控制代码的编写和整合工作!	"
"		"
"	·   2013/03/08: 调试的工作真的好累! 终于诞生了自认完美的报价排版模拟系统V1.2版!	"
"		"
"	·   2013/04/10: 添加快捷键操作提高效率! 呵呵!	"
"		"
"	·   2013/08/24: V1.3版本升级：闲来无事做了一些小bug的优化更新!	"
"		"
"	·   2013/12/29: V1.4版本升级：自定义底层数据更新终于完成！	"
"		"
"	·   2014/01/01: V1.5版本升级：数据记功能优化！	"
"		"
"	·   2014/01/07: 添加选择对象数据记忆功能	"
"		"
"	使用说明：	"
"		"
"	¨        工件尺寸：显示工件X方向尺寸和Y方向尺寸两部份及零件长宽	"
"		"
"	¨        工件资料：显示工件的名称、材质、板厚，	"
"		"
"	¨        板材尺寸：显示3种选项：①1220*1220 ②1220*2440 ③自定义。	"
"		"
"	¨        间距的设定：显示工件的排版间距和数冲的夹钳安全间距。	"
"		"
"	¨        成本及排版信息输出窗：显示程序计算完成的工件成本及排版信息。	"
"		"
"	¨        自动工件的抓取：自动在屏幕上抓取工件相关信息。 　 	"
"		"
"	¨        偏置：设置零件原点偏置座标。	"
"		"
"	¨        数量：设置零件排版横向及纵向数量。	"
"		"
"	¨        面积及重量：材料利用效率数据。	"
"		"
"	¨        帮助：本程序的版本及使用相关说明。	"
"		"
"	¨        排版模拟：程序的主功能！零件根据用户输入或抓取的相关信息进行排版模拟。	"
"		"
"	¨        取消：最后是退出按钮显示结束语”感谢您使用程序！祝您生活愉快！！”。	"
"		"
"	¨        结语: 后续将偿试新的程序算法!以期为您提供更合理的程序功能！	"
"		"
"	¨        若您在使用过程中有任何疑问及困惑请联系本作者！鄙人将竭诚为您服务！	"
"		"
"	¨        在此感谢爱人昝安霞女士的不辞辛劳的照顾与包容！	"
"		"
"	¨        作者：浪子   更多CAD插件访问 http://zhenyoudong1.blog.163.com/	"
"		"
"	                                                  2014年1月7日  于  深圳公明楼村	"
))

(dcl-writ MJZ1 ".dcl")
(dcl-writ MJZ2 ".LDB")
(dcl-writ MJZ3 ".ini")
(dcl-writ MJZ4 ".txt")

;;;图层设置
(command "layer" "n" "0"  "l" "continuous" "0" "c" "7" "0" "")
(command "layer" "n" "BASE"  "l" "phantom2" "BASE" "c" "1" "BASE" "")
(command "layer" "n" "BEND"  "l" "continuous" "BEND" "c" "3" "BEND" "")
(command "layer" "n" "BENDHID"  "l" "DASHED" "BENDHID" "c" "3" "BENDHID" "")
(command "layer" "n" "CENTER"  "l" "center2" "CENTER" "c" "1" "CENTER" "")
(command "layer" "n" "DEFINE"  "l" "continuous" "0" "c" "7" "0" "")
(command "layer" "n" "DIM"  "l" "continuous" "DIM" "c" "4" "DIM" "")
(command "layer" "n" "FORM"  "l" "continuous" "FORM" "c" "180" "FORM" "")
(command "layer" "n" "HATCH"  "l" "continuous" "HATCH" "c" "42" "HATCH" "")
(command "layer" "n" "HIDDEN"  "l" "DASHED" "HIDDEN" "c" "2" "HIDDEN" "")
(command "layer" "n" "LASER"  "l" "continuous" "LASER" "c" "1" "LASER" "")
(command "layer" "n" "MARK"  "l" "continuous" "MARK" "c" "3" "MARK" "")
(command "layer" "n" "NCT"  "l" "continuous" "NCT" "c" "6" "NCT" "")
(command "layer" "n" "PREP"  "l" "continuous" "PREP" "c" "5" "PREP" "")
(command "layer" "n" "PREPHID"  "l" "DASHED" "PREPHID" "c" "5" "PREPHID" "")
(command "layer" "n" "ZCJG"  "l" "continuous" "ZCJG" "c" "3" "ZCJG" "")
