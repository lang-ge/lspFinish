;;; ***********************************************
;;; 打印机切换dos_clipboard
(defun C:V6 (/ olddynmode prna str key)
  (vl-load-com)
  (setvar "cmdecho" 0)
  (setq olddynmode (getvar "dynmode"))
  (if (/= 1 olddynmode)
    (setvar "dynmode" 1)
  )
  (setq prna (defultprint))
  (startapp "wscript.exe" (strcat "\"" (findfile "pts.vbs") "\""))
;;  (SendKeys "")
  (vl-cmdf "delay" 200) 
  (setq str (GET-CLIP-STRING))
  (if (= str "1")
    (progn
      (initget "1 2 3")
      (setq key (getkword (acet-str-format "\n检测到打印机为暂停状态![恢复打印(1)/放弃^-^(2)/查看队列(3)]/<恢复打印>:")))
      (cond 
        ((eq key "1")
         (startapp (strcat "rundll32 printui.dll,PrintUIEntry /Xs /n \"" prna "\" status Resume"))
        )
        ((eq key "2")
         (princ "程序退出!")
        )
        ((eq key "3")
         (startapp (strcat "rundll32 printui.dll,PrintUIEntry /o /n \"" prna "\""))
        )
      )
    )
    (progn
      (initget "1 2 3")
      (setq key (getkword (acet-str-format "\n检测到打印机为恢复状态![暂停打印(1)/放弃^-^(2)/查看队列(3)]/<暂停打印>:")))
      (cond 
        ((eq key "1")
         (startapp (strcat "rundll32 printui.dll,PrintUIEntry /Xs /n \"" prna "\" status Pause"))
        )
        ((eq key "2")
         (princ "程序退出!")
        )
        ((eq key "3")
         (startapp (strcat "rundll32 printui.dll,PrintUIEntry /o /n \"" prna "\""))
        )
      )
    )
  )
  (setvar "dynmode" olddynmode)
  (princ)
)
